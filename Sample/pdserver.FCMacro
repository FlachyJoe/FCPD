#############################

ADDRESS = 'localhost'
PORT = 8888

#What to do with PD message
def pdMsgProcessor(words):
	Msg(words)
	Msg("\r\n")
	currentPatch = words[0]
	if words[1] == "get":
		if words[2] == "vector":
			return  App.Base.Vector(0, 1, 2)

#############################
import select
import socket

run = True
userTerminate=False
remote_address=""

def terminate(btn):
	global run, userTerminate
	run = False
	userTerminate = btn is not None

def spacer(strMessage):
	return strMessage.translate(str.maketrans('', '', '(),;' ))

def pdMsgListProcessor(msgList):
	returnValue = []	
	for msg in msgList:
		#remove trailing semicolon and newline
		msg = msg[:-2]
		#split words
		words = msg.split(' ')
		if words[0] == 'initrcv':
			output_socket.connect((remote_address, int(words[1])))
			Msg("Callback initialized to %s:%s\r\n" % (remote_address, words[1]))
		elif words[0] == 'close':
			terminate(None)
		else:
			ret = pdMsgProcessor(words)
			if type(ret) != str:
				ret = str(ret)
			#callback include current patch id ($0 in PD) to route the message and a trailing semicolon
			returnValue.append("%s %s;" % (words[0], spacer(ret)) )
	return returnValue

#Prepare dialog
from PySide import QtGui
mb = QtGui.QMessageBox()
mb.setIcon(mb.Icon.Warning)
mb.setText("Wait for PureData connection...")
mb.setWindowTitle("PureData connection")
mb.setModal(False)
mb.setStandardButtons(mb.StandardButton.Close)
mb.buttonClicked.connect(terminate)
mb.show()

input_socket = socket.socket(socket.AF_INET, socket.SOCK_STREAM)
input_socket.setsockopt(socket.SOL_SOCKET, socket.SO_REUSEADDR, 1)

output_socket = socket.socket(socket.AF_INET, socket.SOCK_STREAM)
output_socket.setsockopt(socket.SOL_SOCKET, socket.SO_REUSEADDR, 1)

try:
	input_socket.bind((ADDRESS, PORT))
	input_socket.listen(5)

	Msg("PDServer : Listening on port %i\r\n" % PORT)
	
	read_list = [input_socket]
	write_list = []
	readBuffer = ""
	while run:
		FreeCADGui.updateGui()
		readable, writable, errored = select.select(read_list, write_list, [],0.1)
		for s in readable:
			if s is input_socket:
				client_socket, address = input_socket.accept()
				read_list.append(client_socket)
				remote_address = address[0]
				Msg("PDServer : Connection from %s:%s\r\n" % address)
				mb.setText("Connected with PureData")
			else:
				data = s.recv(1024)
				if data:
					readBuffer += data.decode('utf8')
					msgList = readBuffer.splitlines(True)
					#is last line complete ?
					lastLine = msgList[-1]
					readBuffer = ""
					if not (lastLine[-1:] == "\n" or lastLine[-1] == ";"):
						msgList =  msgList[:-1]
						readBuffer = lastLine
						Msg(readBuffer + ">>%i<<\r\n" % ord(lastLine[-1]))
					retList = pdMsgListProcessor(msgList)
					if retList:
						for ret in retList:
							bret=bytes(ret, "utf8")
							n=output_socket.send(bret)
				else:
					s.close()
					Msg("close connection\r\n")
					read_list.remove(s)

except:
	Err("PDServer : %s\r\n" % sys.exc_info()[1])
finally:
	try:
		input_socket.shutdown(socket.SHUT_RDWR)
	except OSError:
		pass
input_socket.close()
output_socket.close()
Msg("PDServer : No more listening port %i\r\n" % PORT)
mb.close()
