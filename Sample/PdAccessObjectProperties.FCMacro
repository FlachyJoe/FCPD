import pdserver

def value_from_str(words):
    return_value = None

    if words[0] in ["Vector", "Pos"]:
        return_value = App.Vector(float(words[1]),float(words[2]),float(words[3]))
    if words[0] in ["Rotation", "Yaw-Pitch-Roll"]:
        return_value = App.Rotation(float(words[1]),float(words[2]),float(words[3]))
    elif words[0]=="Placement":
        return_value =App.Placement(value_from_str(words[1:5]), value_from_str(words[5:]))

    return return_value


#What to do with unregistered PD message
def pdMsgProcessor(words):
    # Nothing !
    pass

def pdGetSet(words):
    try:
        if words[1] == "get":
            if words[2] == "selection":
                sel = Gui.Selection.getSelection()
                objList = [obj.Name for obj in sel]
                return objList
            elif words[2] == "property":
                obj = App.ActiveDocument.getObject(words[3])
                return obj.getPropertyByName(words[4])
        elif words[1] == "set":
            if words[2] == "property":
                obj = App.ActiveDocument.getObject(words[3])
                return setattr(obj,words[4],value_from_str(words[5:]))
    except:
        return "ERROR %s" % sys.exc_info()[1]

pd_server = pdserver.PureDataServer('localhost', 8888)
pd_server.default_message_handler=pdMsgProcessor
pd_server.register_message_handler(["get","set"], pdGetSet)
pd_server.run()
