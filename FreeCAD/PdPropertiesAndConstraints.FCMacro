import pdserver

def value_from_str(words):
    return_value = None

    if words[0] in ["Vector", "Pos"]:
        return_value = App.Vector(float(words[1]),float(words[2]),float(words[3]))
    elif words[0] in ["Rotation", "Yaw-Pitch-Roll", "Rot"]:
        return_value = App.Rotation(float(words[1]),float(words[2]),float(words[3]))
    elif words[0]=="Placement":
        return_value = App.Placement(value_from_str(words[1:5]), value_from_str(words[5:]))
    else:
        try :
            return_value = App.Units.parseQuantity(''.join(words))
        except:
            Log(sys.exc_info())
            Log("[%s] \r\n" % words[0])
    return return_value


#What to do with unregistered PD message
def pdMsgProcessor(words):
    # Nothing !
    pass

def pdGet(words):
    if words[2] == "selection":
        sel = Gui.Selection.getSelection()
        objList = [obj.Name for obj in sel]
        return objList
    elif words[2] == "property":
        obj = App.ActiveDocument.getObject(words[3])
        return obj.getPropertyByName(words[4])
    elif words[2] == "constraint":
        skc = App.ActiveDocument.getObject(words[3])
        return skc.getDatum(words[4])

def pdSet(words):
    if words[2] == "property":
        obj = App.ActiveDocument.getObject(words[3])
        return setattr(obj,words[4], value_from_str(words[5:]))
    elif words[2] == "constraint":
        skc = App.ActiveDocument.getObject(words[3])
        return skc.setDatum(words[4],  value_from_str(words[5:]))

def pdCopy(words):
    obj = App.ActiveDocument.getObject(words[2])
    obj2 = App.ActiveDocument.copyObject(obj, False, False)
    for prt in [tpl[0] for tpl in obj.Parents]:
        prt.addObject(obj2)
    return obj2.Name

def pdDelete(words):
    for obj in words[2:]:
        App.ActiveDocument.removeObject(obj)

def pdPart(words):
    if words[2] == "create":
        if words[3] == "Loft":
            doc = App.ActiveDocument
            loft = doc.addObject('Part::Loft','Loft')
            loft.Sections=[doc.getObject(name) for name in words[4:]]
            loft.Solid = True
            return loft.Name

def pdRecompute(words):
        App.ActiveDocument.recompute()


pd_server = pdserver.PureDataServer('localhost', 8888)
pd_server.default_message_handler = pdMsgProcessor
# pd_server.error_handler = pd_server.error_handler
pd_server.register_message_handler(["get"], pdGet)
pd_server.register_message_handler(["set"], pdSet)
pd_server.register_message_handler(["Part"], pdPart)
pd_server.register_message_handler(["copy"], pdCopy)
pd_server.register_message_handler(["delete"], pdDelete)
pd_server.register_message_handler(["recompute"], pdRecompute)
pd_server.run()
